Attribute VB_Name = "modOCRDLG"
Option Explicit

'
' Example showing how to open and close the reference file dialog
'
'
'

Declare Function mdlDialog_closeCommandQueue Lib "stdmdlbltin.dll" (ByVal dbP As Long) As Long
Declare Function mdlDialog_find Lib "stdmdlbltin.dll" (ByVal dialogId As Long, ByRef ownerId As Integer) As Long

Sub openRefDlg()
    CadInputQueue.SendCommand "MDL KEYIN REF DIALOG REFERENCE"
End Sub
Sub closeRefDlg()
    mdlDialog_closeCommandQueue mdlDialog_find(-7, 0)
    CommandState.StartDefaultCommand
End Sub
