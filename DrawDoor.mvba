Attribute VB_Name = "classDD"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents

Dim ptNum As Integer
Dim ptP As Point3d

Private Sub IPrimitiveCommandEvents_Cleanup()
    
End Sub
' ===============================================================================
' DATAPOINT EVENT HANDLER.
'
' Ramsey Systems, Inc. March 15, 2002
' FREE ROTATE - March 26, 2002 - requires rPt (3rd point) for rotation.
' ===============================================================================
Private Sub IPrimitiveCommandEvents_DataPoint(point As Point3d, ByVal view As view)
    ' NO MIRROR AND NO FREE ROTATE
    If Not formDD.chkMirror And Not formDD.chkRotate Then
        pf_dynDrawDoor point, point, point, view, msdDrawingModeNormal
        CommandState.StartPrimitive Me
    End If
    
    ' MIRROR ONLY or FREE ROTATE ONLY
    If (Not formDD.chkMirror And formDD.chkRotate) Or (formDD.chkMirror And Not formDD.chkRotate) Then
        If ptNum = 0 Then
            ptNum = 1
            ptP = point
        Else
            pf_dynDrawDoor point, ptP, point, view, msdDrawingModeNormal
            CommandState.StartPrimitive Me
        End If
    End If

    ' MIRROR AND FREE ROTATE BOTH
    If formDD.chkMirror And formDD.chkRotate Then
        If ptNum = 0 Then
            ptNum = 1
            ptP = point
        ElseIf ptNum = 1 Then
            ptNum = 2
        Else
            pf_dynDrawDoor point, ptP, point, view, msdDrawingModeNormal
            CommandState.StartPrimitive Me
        End If
    End If
End Sub
' ===============================================================================
' DYNAMIC HANDLER. - CALLS ROUTINE
'
' Ramsey Systems, Inc. March 15, 2002
' FREE ROTATE - March 26, 2002
' ===============================================================================
Private Sub IPrimitiveCommandEvents_Dynamics(point As Point3d, ByVal view As view, ByVal DrawMode As MsdDrawingMode)
    ' NO MIRROR AND NO FREE ROTATE
    If Not formDD.chkMirror And Not formDD.chkRotate Then
        pf_dynDrawDoor point, point, point, view, DrawMode
    End If
    
    ' MIRROR ONLY or FREE ROTATE ONLY
    If (Not formDD.chkMirror And formDD.chkRotate) Or (formDD.chkMirror And Not formDD.chkRotate) Then
        If ptNum = 0 Then
            pf_dynDrawDoor point, point, point, view, DrawMode
        Else
            pf_dynDrawDoor point, ptP, point, view, DrawMode
        End If
    End If
    
    ' MIRROR AND FREE ROTATE BOTH
    If formDD.chkMirror And formDD.chkRotate Then
        If ptNum = 0 Then
            pf_dynDrawDoor point, point, point, view, DrawMode
        ElseIf ptNum = 1 Then
            pf_dynDrawDoor point, ptP, point, view, DrawMode
        Else
            pf_dynDrawDoor point, ptP, point, view, DrawMode
        End If
    End If
End Sub

Private Sub IPrimitiveCommandEvents_Keyin(ByVal KeyIn As String)

End Sub
' ===============================================================================
' RESET EVENT HANDLER.
'
' Ramsey Systems, Inc. March 15, 2002
' ===============================================================================
Private Sub IPrimitiveCommandEvents_Reset()
    CommandState.StartDefaultCommand
End Sub
' ===============================================================================
' PRIMITIVE INITIALIZATION.
'
' Ramsey Systems, Inc. April 18, 2002
' ===============================================================================
Private Sub IPrimitiveCommandEvents_Start()
    ' INITIALIZE DATAPOINT COUNTER
    ptNum = 0
        
    CommandState.EnableAccuSnap
    CommandState.StartDynamics
End Sub
' ===============================================================================
' pf_dynDrawDoor - DRAW ROUTINE : : : DOOR
'
' Ramsey Systems, Inc. April 18, 2002
' ===============================================================================
Private Sub pf_dynDrawDoor(mPt As Point3d, point As Point3d, rPt As Point3d, view As view, DrawMode As MsdDrawingMode)
    Dim linePts() As Point3d, constructPt As Point3d, origin As Point3d, jamVertices() As Point3d
    Dim oLine() As LineElement
    Dim oArc As ArcElement
    Dim oCell As CellElement
    Dim oElts() As Element
    Dim i As Integer
    
    ' DRAW ABOUT 0,0,0
    constructPt.X = 0
    constructPt.Y = 0
    constructPt.Z = 0
          
    ' DRAW LINES FOR THE TAP FROM EDGE
    ReDim linePts(0 To 1)
    ReDim oLine(0 To 2)
    
    ' DRAW THE RIGHT DOOR
    linePts(0) = constructPt
    linePts(0).X = constructPt.X + formDD.txtDoorSize / 2
    linePts(1) = linePts(0)
    linePts(1).Y = linePts(0).Y + formDD.txtDoorSize
    Set oLine(0) = CreateLineElement1(Nothing, linePts)
    
    ' DRAW FIRST JAM
    ReDim jamVertices(0 To 4)
    
    jamVertices(0) = linePts(0)
    jamVertices(0).X = jamVertices(0).X + formDD.txtJamSize / 2   ' Developer's Whim - a detail that needs to be defined by the spec
    jamVertices(0).Y = formDD.txtJamSize / 2
    jamVertices(1) = jamVertices(0)
    jamVertices(1).X = jamVertices(0).X - formDD.txtJamSize / 2
    jamVertices(2) = jamVertices(1)
    jamVertices(2).Y = jamVertices(1).Y - formDD.txtJamSize
    jamVertices(3) = jamVertices(2)
    jamVertices(3).X = jamVertices(2).X + formDD.txtJamSize / 2
    jamVertices(4) = jamVertices(0)
    Set oLine(1) = CreateLineElement1(Nothing, jamVertices)
    
    ' DRAW SECOND JAM
    jamVertices(0) = constructPt
    jamVertices(0).X = constructPt.X - formDD.txtDoorSize / 2 - formDD.txtJamSize / 2
    jamVertices(0).Y = formDD.txtJamSize / 2
    jamVertices(1) = jamVertices(0)
    jamVertices(1).X = jamVertices(0).X + formDD.txtJamSize / 2
    jamVertices(2) = jamVertices(1)
    jamVertices(2).Y = jamVertices(1).Y - formDD.txtJamSize
    jamVertices(3) = jamVertices(2)
    jamVertices(3).X = jamVertices(2).X - formDD.txtJamSize / 2
    jamVertices(4) = jamVertices(0)
    Set oLine(2) = CreateLineElement1(Nothing, jamVertices)
    
    ' DRAW DOOR SWEEP
    Set oArc = CreateArcElement2(Nothing, oLine(0).StartPoint, formDD.txtDoorSize, formDD.txtDoorSize, view.Rotation, Pi / 2, Pi / 2)
    
    ' FORCE THE ARC WEIGHT TO BE 0
    oArc.LineWeight = 0
    
    ' ADD ELEMENTS TO CELL
    ReDim oElts(0 To 3)
    
    For i = 0 To 2
        Set oElts(i) = oLine(i)
    Next
    
    Set oElts(3) = oArc
    
    Set oCell = CreateCellElement1("DEMODOOR", oElts, constructPt, False)
    
    origin = point
    
    Dim Eltrans As Transform3d
    Eltrans = Transform3dFromXYZ(origin.X, origin.Y, origin.Z)
    oCell.Transform Eltrans
    
    ' HANDLE ACTIVE ROTATION
    Eltrans = Transform3dFromMatrix3dAndFixedPoint3d(Matrix3dFromAxisAndRotationAngle(2, ActiveSettings.angle), point)
    oCell.Transform Eltrans
        
    ' HANDLE SCALE REQUEST
    Dim skale As Point3d
    skale = ActiveSettings.Scale
    Eltrans = Transform3dFromMatrix3dAndFixedPoint3d(Matrix3dFromScaleFactors(skale.X, skale.Y, skale.Z), point)
    oCell.Transform Eltrans
    
    ' HANDLE MIRROR REQUESTS
    If ptNum = 1 And formDD.chkMirror Then
        Dim stat As Integer
        stat = pf_mirrorFitting(oCell, mPt, point, view)
    End If

    ' HANDLE FREE ROTATION - AFTER MIRROR REQUEST
    If (formDD.chkRotate And formDD.chkMirror And ptNum = 2) Or (formDD.chkRotate And Not formDD.chkMirror And ptNum = 1) Then
        Dim rAngle As Double, isFlipped As Boolean
        
        rAngle = getAngle(point, rPt, isFlipped)
        If Not isFlipped Then rAngle = rAngle + Pi
        Eltrans = Transform3dFromMatrix3dAndFixedPoint3d(Matrix3dFromAxisAndRotationAngle(2, rAngle), point)
        oCell.Transform Eltrans
    End If
    
    ' DRAW THE CELL
    If DrawMode = msdDrawingModeNormal Then
        ActiveModelReference.AddElement oCell
        oCell.Redraw DrawMode
    Else
        oCell.Redraw DrawMode
    End If
    
    For i = 0 To 2
        Set oLine(i) = Nothing
        Set oElts(i) = Nothing
    Next

    Set oElts(3) = Nothing
    Set oCell = Nothing
End Sub

Attribute VB_Name = "classDblCode"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit

Implements IPrimitiveCommandEvents

Dim ptNum As Integer
Dim ptP As Point3d

Private Sub IPrimitiveCommandEvents_Cleanup()
    
End Sub
' ===============================================================================
' DATAPOINT EVENT HANDLER.
'
' Ramsey Systems, Inc. March 15, 2002
' FREE ROTATE - March 26, 2002 - requires rPt (3rd point) for rotation.
' ===============================================================================
Private Sub IPrimitiveCommandEvents_DataPoint(point As Point3d, ByVal view As view)
    ' NO MIRROR AND NO FREE ROTATE
    If Not formDD.chkMirror And Not formDD.chkRotate Then
        pf_dynDrawDoor point, point, point, view, msdDrawingModeNormal
        CommandState.StartPrimitive Me
    End If
    
    ' MIRROR ONLY or FREE ROTATE ONLY
    If (Not formDD.chkMirror And formDD.chkRotate) Or (formDD.chkMirror And Not formDD.chkRotate) Then
        If ptNum = 0 Then
            ptNum = 1
            ptP = point
        Else
            pf_dynDrawDoor point, ptP, point, view, msdDrawingModeNormal
            CommandState.StartPrimitive Me
        End If
    End If

    ' MIRROR AND FREE ROTATE BOTH
    If formDD.chkMirror And formDD.chkRotate Then
        If ptNum = 0 Then
            ptNum = 1
            ptP = point
        ElseIf ptNum = 1 Then
            ptNum = 2
        Else
            pf_dynDrawDoor point, ptP, point, view, msdDrawingModeNormal
            CommandState.StartPrimitive Me
        End If
    End If
End Sub
' ===============================================================================
' DYNAMIC HANDLER. - CALLS ROUTINE
'
' Ramsey Systems, Inc. March 15, 2002
' FREE ROTATE - March 26, 2002
' ===============================================================================
Private Sub IPrimitiveCommandEvents_Dynamics(point As Point3d, ByVal view As view, ByVal DrawMode As MsdDrawingMode)
    ' NO MIRROR AND NO FREE ROTATE
    If Not formDD.chkMirror And Not formDD.chkRotate Then
        pf_dynDrawDoor point, point, point, view, DrawMode
    End If
    
    ' MIRROR ONLY or FREE ROTATE ONLY
    If (Not formDD.chkMirror And formDD.chkRotate) Or (formDD.chkMirror And Not formDD.chkRotate) Then
        If ptNum = 0 Then
            pf_dynDrawDoor point, point, point, view, DrawMode
        Else
            pf_dynDrawDoor point, ptP, point, view, DrawMode
        End If
    End If
    
    ' MIRROR AND FREE ROTATE BOTH
    If formDD.chkMirror And formDD.chkRotate Then
        If ptNum = 0 Then
            pf_dynDrawDoor point, point, point, view, DrawMode
        ElseIf ptNum = 1 Then
            pf_dynDrawDoor point, ptP, point, view, DrawMode
        Else
            pf_dynDrawDoor point, ptP, point, view, DrawMode
        End If
    End If
End Sub

Private Sub IPrimitiveCommandEvents_Keyin(ByVal KeyIn As String)

End Sub
' ===============================================================================
' RESET EVENT HANDLER.
'
' Ramsey Systems, Inc. March 15, 2002
' ===============================================================================
Private Sub IPrimitiveCommandEvents_Reset()
    CommandState.StartDefaultCommand
End Sub
' ===============================================================================
' PRIMITIVE INITIALIZATION.
'
' Ramsey Systems, Inc. April 18, 2002
' ===============================================================================
Private Sub IPrimitiveCommandEvents_Start()
    ' INITIALIZE DATAPOINT COUNTER
    ptNum = 0
        
    CommandState.EnableAccuSnap
    CommandState.StartDynamics
End Sub
' ===============================================================================
' pf_dynDrawDoor - DRAW ROUTINE : : : DOOR
'
' Ramsey Systems, Inc. April 18, 2002
' ===============================================================================
Private Sub pf_dynDrawDoor(mPt As Point3d, point As Point3d, rPt As Point3d, view As view, DrawMode As MsdDrawingMode)
    Dim linePts() As Point3d, constructPt As Point3d, origin As Point3d, jamVertices() As Point3d
    Dim oLine() As LineElement
    Dim oArc As ArcElement
    Dim oArc2 As ArcElement
    Dim oCell As CellElement
    Dim oElts() As Element
    Dim i As Integer
    
    ' DRAW ABOUT 0,0,0
    constructPt.X = 0
    constructPt.Y = 0
    constructPt.Z = 0
          
    ' DRAW LINES FOR THE TAP FROM EDGE
    ReDim linePts(0 To 1)
    ReDim oLine(0 To 3)
    
    ' DRAW THE RIGHT DOOR
    linePts(0) = constructPt
    linePts(0).X = constructPt.X + formDD.txtDoorSize / 2
    linePts(1) = linePts(0)
    linePts(1).Y = linePts(0).Y + formDD.txtDoorSize / 2
    Set oLine(0) = CreateLineElement1(Nothing, linePts)
    
    ' DRAW THE LEFT DOOR
    linePts(0) = constructPt
    linePts(0).X = constructPt.X - formDD.txtDoorSize / 2
    linePts(1) = linePts(0)
    linePts(1).Y = linePts(0).Y + formDD.txtDoorSize / 2
    Set oLine(1) = CreateLineElement1(Nothing, linePts)
    
    ' DRAW FIRST JAM
    ReDim jamVertices(0 To 4)
    
    jamVertices(0) = oLine(0).StartPoint
    jamVertices(0).X = jamVertices(0).X + formDD.txtJamSize / 2   ' Developer's Whim - a detail that needs to be defined by the spec
    jamVertices(0).Y = formDD.txtJamSize / 2
    jamVertices(1) = jamVertices(0)
    jamVertices(1).X = jamVertices(0).X - formDD.txtJamSize / 2
    jamVertices(2) = jamVertices(1)
    jamVertices(2).Y = jamVertices(1).Y - formDD.txtJamSize
    jamVertices(3) = jamVertices(2)
    jamVertices(3).X = jamVertices(2).X + formDD.txtJamSize / 2
    jamVertices(4) = jamVertices(0)
    Set oLine(2) = CreateLineElement1(Nothing, jamVertices)
    
    ' DRAW SECOND JAM
    jamVertices(0) = constructPt
    jamVertices(0).X = constructPt.X - formDD.txtDoorSize / 2 - formDD.txtJamSize / 2
    jamVertices(0).Y = formDD.txtJamSize / 2
    jamVertices(1) = jamVertices(0)
    jamVertices(1).X = jamVertices(0).X + formDD.txtJamSize / 2
    jamVertices(2) = jamVertices(1)
    jamVertices(2).Y = jamVertices(1).Y - formDD.txtJamSize
    jamVertices(3) = jamVertices(2)
    jamVertices(3).X = jamVertices(2).X - formDD.txtJamSize / 2
    jamVertices(4) = jamVertices(0)
    Set oLine(3) = CreateLineElement1(Nothing, jamVertices)
    
    ' DRAW DOOR SWEEP
    Set oArc = CreateArcElement2(Nothing, oLine(0).StartPoint, formDD.txtDoorSize / 2, formDD.txtDoorSize / 2, view.Rotation, Pi / 2, Pi / 2)
    Set oArc2 = CreateArcElement2(Nothing, oLine(1).StartPoint, formDD.txtDoorSize / 2, formDD.txtDoorSize / 2, view.Rotation, 0, Pi / 2)
    
    ' FORCE THE ARC WEIGHT TO BE 0
    oArc.LineWeight = 0
    oArc2.LineWeight = 0
    
    ' ADD ELEMENTS TO CELL
    ReDim oElts(0 To 5)
    
    For i = 0 To 3
        Set oElts(i) = oLine(i)
    Next
    
    Set oElts(4) = oArc
    Set oElts(5) = oArc2
    
    Set oCell = CreateCellElement1("DEMODOOR", oElts, constructPt, False)
    
    origin = point
    
    Dim Eltrans As Transform3d
    Eltrans = Transform3dFromXYZ(origin.X, origin.Y, origin.Z)
    oCell.Transform Eltrans
    
    ' HANDLE ACTIVE ROTATION
    Eltrans = Transform3dFromMatrix3dAndFixedPoint3d(Matrix3dFromAxisAndRotationAngle(2, ActiveSettings.angle), point)
    oCell.Transform Eltrans
        
    ' HANDLE SCALE REQUEST
    Dim skale As Point3d
    skale = ActiveSettings.Scale
    Eltrans = Transform3dFromMatrix3dAndFixedPoint3d(Matrix3dFromScaleFactors(skale.X, skale.Y, skale.Z), point)
    oCell.Transform Eltrans
    
    ' HANDLE MIRROR REQUESTS
    If ptNum = 1 And formDD.chkMirror Then
        Dim stat As Integer
        stat = pf_mirrorFitting(oCell, mPt, point, view)
    End If

    ' HANDLE FREE ROTATION - AFTER MIRROR REQUEST
    If (formDD.chkRotate And formDD.chkMirror And ptNum = 2) Or (formDD.chkRotate And Not formDD.chkMirror And ptNum = 1) Then
        Dim rAngle As Double, isFlipped As Boolean
        
        rAngle = getAngle(point, rPt, isFlipped)
        If Not isFlipped Then rAngle = rAngle + Pi
        Eltrans = Transform3dFromMatrix3dAndFixedPoint3d(Matrix3dFromAxisAndRotationAngle(2, rAngle), point)
        oCell.Transform Eltrans
    End If
    
    ' DRAW THE CELL
    If DrawMode = msdDrawingModeNormal Then
        ActiveModelReference.AddElement oCell
        oCell.Redraw DrawMode
    Else
        oCell.Redraw DrawMode
    End If
    
    For i = 0 To 3
        Set oLine(i) = Nothing
        Set oElts(i) = Nothing
    Next
    
    For i = 0 To 5
    Set oElts(i) = Nothing
    Next
    Set oCell = Nothing
End Sub

Attribute VB_Name = "formDD"
Attribute VB_Base = "0{2C7E9949-8F5A-4016-9EF1-E51633CE819F}{0F20D554-65B8-4D42-90CE-FAEAA8A3DD8A}"
Attribute VB_GlobalNameSpace = False
Attribute VB_Creatable = False
Attribute VB_PredeclaredId = True
Attribute VB_Exposed = False
Attribute VB_TemplateDerived = False
Attribute VB_Customizable = False
Private Sub CommandButton1_Click()
    CommandState.StartPrimitive New classDD
End Sub

Private Sub txtDoorSize_Change()
    If Not IsNumeric(formDD.txtDoorSize.Text) Then
        formDD.txtDoorSize.Text = 3
    End If
End Sub

Attribute VB_Name = "modDD"
' =================================================================================
' getAngle - CALCULATE THE ANGLE BASED ON DP1 AND DP2 RETURNS ANGLE IN RADIANS
'
' 12-11-01 RAMSEY SYSTEMS, INC.
' =================================================================================
Public Function getAngle(startPt As Point3d, endPt As Point3d, flipped As Boolean) As Double
    Dim vec1 As Point3d
    Dim vec2 As Point3d
    Dim angle As Double
    
    flipped = False
    
    If (startPt.X <= endPt.X And startPt.Y < endPt.Y) Or (startPt.X > endPt.X And startPt.Y < endPt.Y) Then
        vec1.X = 1
    Else
        vec1.X = -1
        flipped = True
    End If
    
    vec1.Y = 0
    vec1.Z = 0
        
    vec2.X = endPt.X - startPt.X
    vec2.Y = endPt.Y - startPt.Y
    vec2.Z = endPt.Z - startPt.Z
    
    angle = Point3dAngleBetweenVectors(vec1, vec2)
    
    getAngle = angle
End Function
' =================================================================================
' ic_handleMirrorTrans - Mirror Cell
'
' 12-11-01 RAMSEY SYSTEMS, INC.
' =================================================================================
Public Function ic_handleMirrorTrans(angle As Double, origin As Point3d, sx As Double, sy As Double, view As view) As Transform3d
    Dim et As Transform3d, cMtx As Matrix3d, cInvMtx As Matrix3d, rInvMtx As Matrix3d, mMtx As Matrix3d, aMtx As Matrix3d, rMtx As Matrix3d

    cMtx = view.Rotation
    rMtx = Matrix3dFromAxisAndRotationAngle(2, angle)
    cInvMtx = Matrix3dInverse(cMtx)
    rInvMtx = Matrix3dInverse(rMtx)
    mMtx = Matrix3dFromScaleFactors(sx, sy, 1)
    aMtx = Matrix3dFromMatrix3dTimesMatrix3dTimesMatrix3d(rMtx, mMtx, rInvMtx)
    aMtx = Matrix3dFromMatrix3dTimesMatrix3dTimesMatrix3d(cMtx, aMtx, cInvMtx)
    et = Transform3dFromMatrix3dAndFixedPoint3d(aMtx, origin)
    ic_handleMirrorTrans = et
    
End Function

' =================================================================================
' pf_mirrorFitting - MIRROR CELL ABOUT AXIS
'
' Ramsey Systems, Inc. March 18, 2002
' =================================================================================
Public Function pf_mirrorFitting(oCell As CellElement, mPt As Point3d, origin As Point3d, view As view) As Integer
        Dim isFlipped As Boolean, mAngle As Double, Eltrans As Transform3d
        
        mAngle = getAngle(origin, mPt, isFlipped)
        'Eltrans = ic_handleMirrorTrans(ActiveSettings.angle, origin, 1, 1, view) ' - - - no mirror
        
       If Not isFlipped And mAngle >= 0 And mAngle <= Pi / 2 Then
            Eltrans = ic_handleMirrorTrans(ActiveSettings.angle, origin, 1, 1, view) ' - - - no mirror
        ElseIf Not isFlipped And mAngle > Pi / 2 And mAngle <= Pi Then
            Eltrans = ic_handleMirrorTrans(ActiveSettings.angle, origin, -1, 1, view) ' - - - mirror across yz-plane
        ElseIf isFlipped And mAngle > 0 And mAngle <= Pi / 2 Then
            Eltrans = ic_handleMirrorTrans(ActiveSettings.angle, origin, -1, -1, view)  ' - - - mirror across xz-plane and yz-plane
        ElseIf isFlipped And mAngle > Pi / 2 And mAngle <= Pi Then
            Eltrans = ic_handleMirrorTrans(ActiveSettings.angle, origin, 1, -1, view)  ' - - - mirror across xz-plane
        End If
        
        oCell.Transform Eltrans
        
        pf_mirrorFitting = 0
End Function
Sub drawDoor()
    Load formDD
    formDD.Show
End Sub
